-- File Name : IPDR.mib
-- Date      : Mon Jun 03 15:43:12 PDT 2005
-- Author    : IPDR Organization.

-- $Id: IPDR.mib,v 1.6 2005/04/21 11:30:21 dmitryk Exp $

IPDR   DEFINITIONS ::= BEGIN
    IMPORTS
        TEXTUAL-CONVENTION
            FROM SNMPv2-TC
        TimeStamp
            FROM SNMPv2-TC
        DisplayString
            FROM RFC1213-MIB
        enterprises, MODULE-IDENTITY, OBJECT-TYPE, Counter32, IpAddress
            FROM SNMPv2-SMI
        enterprises
            FROM RFC1155-SMI;

    ipdr MODULE-IDENTITY
        LAST-UPDATED    "200502271539Z"
        ORGANIZATION    "IPDR Organization.
Copyright (c) 2005 IPDR Organization, All Rights Reserved."
        CONTACT-INFO    "Technical Support Organization
2005 IPDR Organization.
Web:   http://www.ipdr.org"
        DESCRIPTION
            "IPDR MIB module."
        REVISION        "200502271539Z"
        DESCRIPTION
            "Removed 'rate' entries (they should be
derived by taking the absolute values
and calculating).

Added serversAcknowledgedRecords and other statistics.

Added commandsString.

Removed consoelStartupScript.

Changed integer32 entries to counter32 where appropriate."
        ::=  {  enterprises  9334  }

-- TEXTUAL-CONVENTIONS --
    BOOLEAN ::= TEXTUAL-CONVENTION
        DISPLAY-HINT    ""
        STATUS          current
        DESCRIPTION     ""
        SYNTAX          INTEGER  { false ( 1 ) , true ( 2 ) }

    org OBJECT IDENTIFIER
        ::=  {  iso  3  }

    dod OBJECT IDENTIFIER
        ::=  {  org  6  }

    internet    OBJECT IDENTIFIER
        ::=  {  dod  1  }

    private OBJECT IDENTIFIER
        ::=  {  internet  4  }

    enterprises OBJECT IDENTIFIER
        ::=  {  private  1  }


-- ----------------------------------------------------------------------------------
-- IPDR MIB
-- ----------------------------------------------------------------------------------

    exporter  OBJECT IDENTIFIER
        ::=  {  ipdr  1  }

    sessionsTable   OBJECT-TYPE
        SYNTAX      SEQUENCE  OF  SessionsEntry
        MAX-ACCESS  not-accessible
        STATUS      current
        DESCRIPTION
            "Table containing the set of sessions configured on the exporter (transmitter)"
        ::=  {  exporter  1  }

    sessionsEntry   OBJECT-TYPE
        SYNTAX      SessionsEntry
        MAX-ACCESS  not-accessible
        STATUS      current
        DESCRIPTION
            "Row in the sessions table"
        INDEX       {  sessionID  }
        ::=  {  sessionsTable  1  }

    SessionsEntry  ::=  SEQUENCE {
        sessionID  Integer32,
        sessionName  OCTET STRING,
        sessionDescription  OCTET STRING,
        sessionTransmittedRecords  Counter32,
        sessionAcknowledgedRecords  Counter32,
        sessionEnqueuedRecords Counter32,
        sessionLostRecords Counter32,
        sessionOutstandingRecords Counter32,
        sessionUnacknowledgedRecords Counter32
        }


    sessionID   OBJECT-TYPE
        SYNTAX          Integer32  (0 .. 2147483647) 
      	MAX-ACCESS      read-only     
        STATUS          current
        DESCRIPTION
            "Session ID"
        ::=  {  sessionsEntry  1  }


    sessionName OBJECT-TYPE
        SYNTAX          OCTET STRING
        MAX-ACCESS      read-only
        STATUS          current
        DESCRIPTION
            "Session name"
        ::=  {  sessionsEntry  2  }


    sessionDescription  OBJECT-TYPE
        SYNTAX          OCTET STRING
        MAX-ACCESS      read-only
        STATUS          current
        DESCRIPTION
            "Session description"
        ::=  {  sessionsEntry  3  }


    sessionTransmittedRecords    OBJECT-TYPE
        SYNTAX          Counter32
        MAX-ACCESS      read-only
        STATUS          current
        DESCRIPTION
            "Total number of records sent for the session (not necessarily acknowleged) (sum of all servers for the session)"
        ::=  {  sessionsEntry  4  }


    sessionAcknowledgedRecords   OBJECT-TYPE
        SYNTAX          Counter32
        MAX-ACCESS      read-only
        STATUS          current
        DESCRIPTION
            "Total number of records acknowledged for the session (sum of all servers for the session)"
        ::=  {  sessionsEntry  5  }


    sessionEnqueuedRecords    OBJECT-TYPE
        SYNTAX          Counter32
        MAX-ACCESS      read-only
        STATUS          current
        DESCRIPTION
            "Total number of records enqueued for the session (on the internal queue)"
        ::=  {  sessionsEntry  6  }


    sessionLostRecords   OBJECT-TYPE
        SYNTAX          Counter32
        MAX-ACCESS      read-only
        STATUS          current
        DESCRIPTION
            "Total number of lost records (because of internal queue overflow)"
        ::=  {  sessionsEntry  7  }


    sessionOutstandingRecords   OBJECT-TYPE
        SYNTAX          Counter32
        MAX-ACCESS      read-only
        STATUS          current
        DESCRIPTION
            "Total number of records for the session on the internal queue and not sent or not acknowledged by any server"
        ::=  {  sessionsEntry  8  }


    sessionUnacknowledgedRecords   OBJECT-TYPE
        SYNTAX          Counter32
        MAX-ACCESS      read-only
        STATUS          current
        DESCRIPTION
            "Total number of records for the session on the internal queue that have been sent to a server but not acknowledged"
        ::=  {  sessionsEntry  9  }


    collectorsTable    OBJECT-TYPE
        SYNTAX      SEQUENCE  OF  CollectorsEntry
        MAX-ACCESS  not-accessible
        STATUS      current
        DESCRIPTION
            "Table containing the set of collectors"
        ::=  {  exporter  2  }


    collectorsEntry    OBJECT-TYPE
        SYNTAX      CollectorsEntry
        MAX-ACCESS  not-accessible
        STATUS      current
        DESCRIPTION
            "Row in the collectors table"
        INDEX       {  collectorAddress, collectorPort  }
        ::=  {  collectorsTable  1  }
 
    CollectorsEntry  ::=  SEQUENCE {
        collectorAddress  IpAddress,
        collectorPort  Integer32,
        collectorConnections  Integer32,
        collectorName  OCTET STRING
        }  

    collectorAddress   OBJECT-TYPE
        SYNTAX          IpAddress
        MAX-ACCESS      read-only
        STATUS          current
        DESCRIPTION
            "IP address of the collector"
        ::=  {  collectorsEntry  1  }


    collectorPort  OBJECT-TYPE
        SYNTAX          Integer32  (0 .. 2147483647)
        MAX-ACCESS      read-only
        STATUS          current
        DESCRIPTION
            "Port number of the collector"
        ::=  {  collectorsEntry  2  }


    collectorConnections  OBJECT-TYPE
        SYNTAX          Integer32
        MAX-ACCESS      read-only
        STATUS          current
        DESCRIPTION
            "Number of connections to collector"
        ::=  {  collectorsEntry  3  }

    collectorName  OBJECT-TYPE
        SYNTAX          OCTET STRING
        MAX-ACCESS      read-only
        STATUS          current
        DESCRIPTION
            "Collector name"
        ::=  {  collectorsEntry  4  }


    templatesTable  OBJECT-TYPE
        SYNTAX      SEQUENCE  OF  TemplatesEntry
        MAX-ACCESS  not-accessible
        STATUS      current
        DESCRIPTION
            "Table containing the templates available in the exporter"
        ::=  {  exporter  3  }

    templatesEntry  OBJECT-TYPE
        SYNTAX      TemplatesEntry
        MAX-ACCESS  not-accessible
        STATUS      current
        DESCRIPTION
            "Row in the templates table"
        INDEX       {  templateID  }
        ::=  {  templatesTable  1  }

    TemplatesEntry  ::=  SEQUENCE {
    	templateSessionID  Integer32,
        templateID  Integer32,
        templateSchemaName  OCTET STRING,
        templateTypeName  OCTET STRING, 
        templateDescription  OCTET STRING,
        templateNumKeys  Integer32
        }

    templateSessionID  OBJECT-TYPE
        SYNTAX          Integer32 
        MAX-ACCESS      read-only
        STATUS          current
        DESCRIPTION
            "Session ID"
        ::=  {  templatesEntry  1  }

    templateID  OBJECT-TYPE
        SYNTAX          Integer32  (0 .. 2147483647) 
      	MAX-ACCESS      read-only
        STATUS          current
        DESCRIPTION
            "Template ID"
        ::=  {  templatesEntry  2  }  
        
    templateSchemaName OBJECT-TYPE
        SYNTAX          OCTET STRING
        MAX-ACCESS      read-only
        STATUS          current
        DESCRIPTION
            "Template schema name"
        ::=  {  templatesEntry  3  }
        
    templateTypeName OBJECT-TYPE
        SYNTAX          OCTET STRING
        MAX-ACCESS      read-only
        STATUS          current
        DESCRIPTION
            "Template type name"
        ::=  {  templatesEntry  4  }   
             
    templateDescription OBJECT-TYPE
        SYNTAX          OCTET STRING
        MAX-ACCESS      read-only
        STATUS          current
        DESCRIPTION
            "Template description"
        ::=  {  templatesEntry  5  }

    templateNumKeys  OBJECT-TYPE
        SYNTAX          Integer32
        MAX-ACCESS      read-only
        STATUS          current
        DESCRIPTION
            "Template keys number"
        ::=  {  templatesEntry  6  }

    keysTable   OBJECT-TYPE
        SYNTAX      SEQUENCE  OF  KeysEntry
        MAX-ACCESS  not-accessible
        STATUS      current
        DESCRIPTION
            "Table containing the set of keys available in the exporter"
        ::=  {  exporter  4  }

    keysEntry   OBJECT-TYPE
        SYNTAX      KeysEntry
        MAX-ACCESS  not-accessible
        STATUS      current
        DESCRIPTION
            "Row in the keys table"
        INDEX       {  keySessionID, keyTemplateID, keyID  }
        ::=  {  keysTable  1  }

    KeysEntry  ::=  SEQUENCE {  
    	keySessionID  Integer32,
        keyTemplateID  Integer32,
        keyID  Integer32,
        keyTypeID  Integer32,
        keyName  OCTET STRING,
        keyLabel  OCTET STRING,
        keyHelp  OCTET STRING,
		keyEnabled Integer32
        }

    keySessionID   OBJECT-TYPE
        SYNTAX          Integer32 (0 .. 2147483647)
        MAX-ACCESS      read-only
        STATUS          current
        DESCRIPTION
            "Session ID of Template of the key"
        ::=  {  keysEntry  1  }

    keyTemplateID   OBJECT-TYPE
        SYNTAX          Integer32 (0 .. 2147483647)
        MAX-ACCESS      read-only
        STATUS          current
        DESCRIPTION
            "Template ID of the key"
        ::=  {  keysEntry  2  }

    keyID   OBJECT-TYPE
        SYNTAX          Integer32 (0 .. 2147483647)
        MAX-ACCESS      read-only
        STATUS          current
        DESCRIPTION
            "Key ID"
        ::=  {  keysEntry  3  }


    keyTypeID   OBJECT-TYPE
        SYNTAX          Integer32
        MAX-ACCESS      read-only
        STATUS          current
        DESCRIPTION
            "Key type identifier"
        ::=  {  keysEntry  4  }

    keyName OBJECT-TYPE
        SYNTAX          OCTET STRING
        MAX-ACCESS      read-only
        STATUS          current
        DESCRIPTION
            "Key name"
        ::=  {  keysEntry  5  }


    keyLabel    OBJECT-TYPE
        SYNTAX          OCTET STRING
        MAX-ACCESS      read-only
        STATUS          current
        DESCRIPTION
            "Key label"
        ::=  {  keysEntry 6  }


    keyHelp OBJECT-TYPE
        SYNTAX          OCTET STRING
        MAX-ACCESS      read-only
        STATUS          current
        DESCRIPTION
            "Key help"
        ::=  {  keysEntry  7  }

    keyEnabled   OBJECT-TYPE
        SYNTAX          Integer32
        MAX-ACCESS      read-only
        STATUS          current
        DESCRIPTION
            "Key Atribute"
        ::=  {  keysEntry  8  }

    keysAttributesTable OBJECT-TYPE
        SYNTAX      SEQUENCE  OF  KeysAttributesEntry
        MAX-ACCESS  not-accessible
        STATUS      current
        DESCRIPTION
            "Table containing the current key attributes per session"
        ::=  {  exporter  5  }

    keysAttributesEntry OBJECT-TYPE
        SYNTAX      KeysAttributesEntry
        MAX-ACCESS  not-accessible
        STATUS      current
        DESCRIPTION
            "Row in the key attributes table"
        INDEX       {  keyAttributesSessionID, keyAttributesTemplateID, keyAttributesID  }
        ::=  {  keysAttributesTable  1  }

    KeysAttributesEntry  ::=  SEQUENCE {
        keyAttributesSessionID  Integer32,
        keyAttributesTemplateID  Integer32,
        keyAttributesID  Integer32,
        keyAttributesTypeID  Integer32,
        keyAttributesName  OCTET STRING,
        keyAttributesLabel  OCTET STRING,
        keyAttributesHelp  OCTET STRING,
		keyAttributesEnabled Integer32
        }

    keyAttributesSessionID   OBJECT-TYPE
        SYNTAX          Integer32  (0 .. 2147483647)
        MAX-ACCESS      read-only
        STATUS          current
        DESCRIPTION
            "Session ID of Template ID of the key"
        ::=  {  keysAttributesEntry  1  }

    keyAttributesTemplateID   OBJECT-TYPE
        SYNTAX          Integer32  (0 .. 2147483647)
        MAX-ACCESS      read-only
        STATUS          current
        DESCRIPTION
            "Template ID of the key"
        ::=  {  keysAttributesEntry  2  }

    keyAttributesID   OBJECT-TYPE
        SYNTAX          Integer32   (0 .. 2147483647)
        MAX-ACCESS      read-only
        STATUS          current
        DESCRIPTION
            "Key ID"
        ::=  {  keysAttributesEntry  3  }


    keyAttributesTypeID   OBJECT-TYPE
        SYNTAX          Integer32
        MAX-ACCESS      read-only
        STATUS          current
        DESCRIPTION
            "Key type identifier"
        ::=  {  keysAttributesEntry  4  }

    keyAttributesName OBJECT-TYPE
        SYNTAX          OCTET STRING
        MAX-ACCESS      read-only
        STATUS          current
        DESCRIPTION
            "Key name"
        ::=  {  keysAttributesEntry  5  }


    keyAttributesLabel    OBJECT-TYPE
        SYNTAX          OCTET STRING
        MAX-ACCESS      read-only
        STATUS          current
        DESCRIPTION
            "Key label"
        ::=  {  keysAttributesEntry 6  }


    keyAttributesHelp OBJECT-TYPE
        SYNTAX          OCTET STRING
        MAX-ACCESS      read-only
        STATUS          current
        DESCRIPTION
            "Key help"
        ::=  {  keysAttributesEntry  7  }

    keyAttributesEnabled   OBJECT-TYPE
        SYNTAX          Integer32
        MAX-ACCESS      read-only
        STATUS          current
        DESCRIPTION
            "Key ID"
        ::=  {  keysAttributesEntry  8  }

    collectorsSessionsTable    OBJECT-TYPE
        SYNTAX      SEQUENCE  OF  CollectorsSessionsEntry
        MAX-ACCESS  not-accessible
        STATUS      current
        DESCRIPTION
            "Table containing the set of sollector to session asociation"
        ::=  {  exporter  6  }


    collectorsSessionsEntry    OBJECT-TYPE
        SYNTAX      CollectorsSessionsEntry
        MAX-ACCESS  not-accessible
        STATUS      current
        DESCRIPTION
            "Row in the collector sessions table"
        INDEX       {  sessionID, collectorName }
        ::=  {  collectorsSessionsTable  1  }
 
    CollectorsSessionsEntry  ::=  SEQUENCE {
        collectorSssionID  Integer32,
        collectorSssionName  OCTET STRING,
        collectorSssionPriority  Integer32
        }
        
    collectorSssionID   OBJECT-TYPE
        SYNTAX          Integer32
        MAX-ACCESS      read-only
        STATUS          current
        DESCRIPTION
            "Session ID"
        ::=  {  collectorsSessionsEntry  1  }

    collectorSssionName OBJECT-TYPE
        SYNTAX          OCTET STRING
        MAX-ACCESS      read-only
        STATUS          current
        DESCRIPTION
            "Collector Name"
        ::=  {  collectorsSessionsEntry  2  }

    collectorSssionPriority   OBJECT-TYPE
        SYNTAX          Integer32
        MAX-ACCESS      read-only
        STATUS          current
        DESCRIPTION
            "Collecotr prioriry in session"
        ::=  {  collectorsSessionsEntry  3  }

    configuration   OBJECT IDENTIFIER
        ::=  {  exporter  7  }

    commands    OBJECT IDENTIFIER
        ::=  {  exporter  8  }

    exporterAddress   OBJECT-TYPE
        SYNTAX          IpAddress
        MAX-ACCESS      read-write
        STATUS          current
        DESCRIPTION
            "IP address of the exporter"
        ::=  {  configuration  1  }

    exporterPort  OBJECT-TYPE
        SYNTAX          Integer32
        MAX-ACCESS      read-write
        STATUS          current
        DESCRIPTION
            "Port number of the exporter"
        ::=  {  configuration  2  }

    vendorString    OBJECT-TYPE
        SYNTAX          OCTET STRING
        MAX-ACCESS      read-write
        STATUS          current
        DESCRIPTION
            "Vendor specific string attached to the exporter"
        ::=  {  configuration  4  }

    console OBJECT IDENTIFIER
        ::=  {  configuration  5  }

    logging OBJECT IDENTIFIER
        ::=  {  configuration  6  }

    windowSize  OBJECT-TYPE
        SYNTAX          Integer32
        MAX-ACCESS      read-only
        STATUS          current
        DESCRIPTION
            "Exporter window size"
        ::=  {  configuration  7  }

    windowTimeout   OBJECT-TYPE
        SYNTAX          Integer32
        MAX-ACCESS      read-only
        STATUS          current
        DESCRIPTION
            "Exporter window timeout"
        ::=  {  configuration  8  }

    templateAckTimeout OBJECT-TYPE
        SYNTAX          Integer32
        MAX-ACCESS      read-only
        STATUS          current
        DESCRIPTION
            "Exporter templates data timeout"
        ::=  {  configuration  9  }

    statisticsInterval  OBJECT-TYPE
        SYNTAX          Integer32
        MAX-ACCESS      read-only
        STATUS          current
        DESCRIPTION
            "Interval between statistics reports"
        ::=  {  configuration  10  }

    transport   OBJECT IDENTIFIER
        ::=  {  configuration  12  }

    queueChunkSize  OBJECT-TYPE
        SYNTAX          Integer32
        MAX-ACCESS      read-write
        STATUS          current
        DESCRIPTION
            "Initial buffer size for the queue"
        ::=  {  configuration  13  }

    queueMaxMemory  OBJECT-TYPE
        SYNTAX          Integer32
        MAX-ACCESS      read-write
        STATUS          current
        DESCRIPTION
            "Maximum memory used by the queue"
        ::=  {  configuration  14  }

    queueInitialNumChunks   OBJECT-TYPE
        SYNTAX          Integer32
        MAX-ACCESS      read-write
        STATUS          current
        DESCRIPTION
            "Initial number of buffers allocated for the queue"
        ::=  {  configuration  15  }

    protocolInfoAddr    OBJECT-TYPE
        SYNTAX          IpAddress
        MAX-ACCESS      read-write
        STATUS          current
        DESCRIPTION
            "Protocol Information IP Address"
        ::=  {  configuration  16  }

    protocolInfoPort    OBJECT-TYPE
        SYNTAX          Integer32
        MAX-ACCESS      read-write
        STATUS          current
        DESCRIPTION
            "Port number of protocol information"
        ::=  {  configuration  17  }

    keepAliveInterval   OBJECT-TYPE
        SYNTAX          Integer32
        MAX-ACCESS      read-write
        STATUS          current
        DESCRIPTION
            "Exporter keep Alive interval"
        ::=  {  configuration  18  }        
              
	autoconnectInterval   OBJECT-TYPE
        SYNTAX          Integer32
        MAX-ACCESS      read-write
        STATUS          current
        DESCRIPTION
            "Exporter autoconnect interval"
        ::=  {  configuration  19  }  
        
	connectResponseTimeout   OBJECT-TYPE
        SYNTAX          Integer32
        MAX-ACCESS      read-write
        STATUS          current
        DESCRIPTION
            "Exporter connect response timeout"
        ::=  {  configuration  20  }        

	waitBestCollectorTimeout   OBJECT-TYPE
        SYNTAX          Integer32
        MAX-ACCESS      read-write
        STATUS          current
        DESCRIPTION
            "Exporter wait for high priority collecot timeout"
        ::=  {  configuration  21  } 

	dataAckTimeInterval   OBJECT-TYPE
        SYNTAX          Integer32
        MAX-ACCESS      read-write
        STATUS          current
        DESCRIPTION
            "Exporter data ACK time interval"
        ::=  {  configuration  22  } 
        
	dataAckSequenceInterval   OBJECT-TYPE
        SYNTAX          Integer32
        MAX-ACCESS      read-write
        STATUS          current
        DESCRIPTION
            "Exporter data ACK Sequence interval"
        ::=  {  configuration  23  }  

    capabilities OBJECT IDENTIFIER
        ::=  {  configuration  24  } 
        
    multiSession   OBJECT-TYPE
        SYNTAX          Integer32
        MAX-ACCESS      read-only
        STATUS          current
        DESCRIPTION
            "Multisession support compability"
        ::=  {  capabilities  1  }

    templateNegotiation   OBJECT-TYPE
        SYNTAX          Integer32
        MAX-ACCESS      read-only
        STATUS          current
        DESCRIPTION
            "Templates negotiation compability"
        ::=  {  capabilities  2  }
 
    structureSupport   OBJECT-TYPE
        SYNTAX          Integer32
        MAX-ACCESS      read-only
        STATUS          current
        DESCRIPTION
            "Template structure support"
        ::=  {  capabilities  3  }

    addCollector OBJECT IDENTIFIER
        ::=  {  commands  1  }

    removeCollector    OBJECT IDENTIFIER
        ::=  {  commands  2  }

    addSession  OBJECT IDENTIFIER
        ::=  {  commands  3  }

    removeSession   OBJECT IDENTIFIER
        ::=  {  commands  4  }

    sessionStart   OBJECT IDENTIFIER
        ::=  {  commands  5  }

    sessionStop   OBJECT IDENTIFIER
        ::=  {  commands  6  }
        
    assignCollectorToSession   OBJECT IDENTIFIER
        ::=  {  commands  7  }

    removeCollectorFromSession   OBJECT IDENTIFIER
        ::=  {  commands  8  }  
        
    reconfigureExporter   OBJECT IDENTIFIER
        ::=  {  commands  9  }
        
    execStringCommand OBJECT IDENTIFIER
    	::=	 { commands   10 }
  
    commandString   OBJECT-TYPE
        SYNTAX          OCTET STRING
        MAX-ACCESS      read-write
        STATUS          current
        DESCRIPTION
            ""
        ::=  {  execStringCommand  1  }
 
    commandResultString   OBJECT-TYPE
        SYNTAX          OCTET STRING
        MAX-ACCESS      read-only
        STATUS          current
        DESCRIPTION
            ""
        ::=  {  execStringCommand  2  }

    consolePort OBJECT-TYPE
        SYNTAX          Integer32
        MAX-ACCESS      read-only
        STATUS          current
        DESCRIPTION
            "Port number of the exporter (transmitter) console"
        ::=  {  console  1  }

    consolePassword OBJECT-TYPE
        SYNTAX          Integer32
        MAX-ACCESS      not-accessible
        STATUS          current
        DESCRIPTION
            "Password for accessing the console (invisible)."
        ::=  {  console  2  }

    loggerAddress   OBJECT-TYPE
        SYNTAX          IpAddress
        MAX-ACCESS      read-only
        STATUS          current
        DESCRIPTION
            "IP address of a syslog compliant logging application"
        ::=  {  logging  1  }

    loggerPort  OBJECT-TYPE
        SYNTAX          Integer32
        MAX-ACCESS      read-only
        STATUS          current
        DESCRIPTION
            "Port number of the logging application"
        ::=  {  logging  2  }

    levels  OBJECT IDENTIFIER
        ::=  {  logging  3  }

    tcpTransport    OBJECT IDENTIFIER
        ::=  {  transport  1  }

    addCollectorName   OBJECT-TYPE
        SYNTAX          OCTET STRING
        MAX-ACCESS      read-write
        STATUS          current
        DESCRIPTION
            "Name of collecotr to be added"
        ::=  {  addCollector  1  }
        
    addCollectorAddress    OBJECT-TYPE
        SYNTAX          IpAddress
        MAX-ACCESS      read-write
        STATUS          current
        DESCRIPTION
            "IP address of collecotr to be added"
        ::=  {  addCollector  2  }

    addCollectorPort   OBJECT-TYPE
        SYNTAX          Integer32
        MAX-ACCESS      read-write
        STATUS          current
        DESCRIPTION
            "Port number of collecotr to be added"
        ::=  {  addCollector  3  }

    addCollectorConnections   OBJECT-TYPE
        SYNTAX          Integer32
        MAX-ACCESS      read-write
        STATUS          current
        DESCRIPTION
            "Number of active connections to collecotr to be added"
        ::=  {  addCollector  4  }

    removeCollectorName   OBJECT-TYPE
        SYNTAX          OCTET STRING
        MAX-ACCESS      read-write
        STATUS          current
        DESCRIPTION
            "Name of collector to remove"
        ::=  {  removeCollector  1  }

    addSessionID    OBJECT-TYPE
        SYNTAX          Integer32
        MAX-ACCESS      read-write
        STATUS          current
        DESCRIPTION
            "ID of session to be added"
        ::=  {  addSession  1  }

    addSessionName  OBJECT-TYPE
        SYNTAX          OCTET STRING
        MAX-ACCESS      read-write
        STATUS          current
        DESCRIPTION
            "Name of session to be added"
        ::=  {  addSession  2  }

    addSessionDescription   OBJECT-TYPE
        SYNTAX          OCTET STRING
        MAX-ACCESS      read-write
        STATUS          current
        DESCRIPTION
            "Description of session to be added"
        ::=  {  addSession  3  }

    removeSessionID OBJECT-TYPE
        SYNTAX          Integer32
        MAX-ACCESS      read-write
        STATUS          current
        DESCRIPTION
            "ID of session to be removed"
        ::=  {  removeSession  1  }
        
    startSessionID OBJECT-TYPE
        SYNTAX          Integer32
        MAX-ACCESS      read-write
        STATUS          current
        DESCRIPTION
            "ID of session to be started"
        ::=  {  sessionStart  1  }
        
    startSessionNegotiate OBJECT-TYPE
        SYNTAX          Integer32
        MAX-ACCESS      read-write
        STATUS          current
        DESCRIPTION
            "ID of session to be started"
        ::=  {  sessionStart  2  }  
        
    stopSessionID OBJECT-TYPE
        SYNTAX          Integer32
        MAX-ACCESS      read-write
        STATUS          current
        DESCRIPTION
            "ID of session to be started"
        ::=  {  sessionStop  1  }

    stopSessionReason OBJECT-TYPE
        SYNTAX          Integer32
        MAX-ACCESS      read-write
        STATUS          current
        DESCRIPTION
            "ID of session to be started"
        ::=  {  sessionStop  2  }

    stopSessionTimeout OBJECT-TYPE
        SYNTAX          Integer32
        MAX-ACCESS      read-write
        STATUS          current
        DESCRIPTION
            "ID of session to be started"
        ::=  {  sessionStop  3  }

    assignCollectorSessionID OBJECT-TYPE
        SYNTAX          Integer32
        MAX-ACCESS      read-write
        STATUS          current
        DESCRIPTION
            "Session ID to asociate with collecotr"
        ::=  {  assignCollectorToSession  1  }
        
    assignCollectorName   OBJECT-TYPE
        SYNTAX          OCTET STRING
        MAX-ACCESS      read-write
        STATUS          current
        DESCRIPTION
            "Collector Name to asociate with session"
        ::=  {  assignCollectorToSession  2  }

    assignCollectorPrioriry OBJECT-TYPE
        SYNTAX          Integer32
        MAX-ACCESS      read-write
        STATUS          current
        DESCRIPTION
            "Collecotr priority in session"
        ::=  {  assignCollectorToSession  3  }
 
 	removeCollectorSessionID OBJECT-TYPE
        SYNTAX          Integer32
        MAX-ACCESS      read-write
        STATUS          current
        DESCRIPTION
            "Session ID from collector will be removed"
        ::=  {  removeCollectorFromSession  1  }
        
    removeCollectorSessionName   OBJECT-TYPE
        SYNTAX          OCTET STRING
        MAX-ACCESS      read-write
        STATUS          current
        DESCRIPTION
            "Collecotr Name to remove from session"
        ::=  {  removeCollectorFromSession  2  }
        
 	reconfigureExporterSet OBJECT-TYPE
        SYNTAX          Integer32
        MAX-ACCESS      read-write
        STATUS          current
        DESCRIPTION
            "just set to 1 to reconfig"
        ::=  {  reconfigureExporter  1  }

        
    moduleExporter    OBJECT-TYPE
        SYNTAX          Integer32
        MAX-ACCESS      read-only
        STATUS          current
        DESCRIPTION
            "Debug level of the Exporter"
        ::=  {  levels  1  }

    moduleQueue OBJECT-TYPE
        SYNTAX          Integer32
        MAX-ACCESS      read-only
        STATUS          current
        DESCRIPTION
            "Debug level of the queue module"
        ::=  {  levels  2  }

    moduleTCP   OBJECT-TYPE
        SYNTAX          Integer32
        MAX-ACCESS      read-only
        STATUS          current
        DESCRIPTION
            "Debug level of the TCP module"
        ::=  {  levels  3  }

    moduleMemory    OBJECT-TYPE
        SYNTAX          Integer32
        MAX-ACCESS      read-only
        STATUS          current
        DESCRIPTION
            "Debug level of the memory module"
        ::=  {  levels  4  }

    moduleProtocol  OBJECT-TYPE
        SYNTAX          Integer32
        MAX-ACCESS      read-only
        STATUS          current
        DESCRIPTION
            "Debug level of the protocol module"
        ::=  {  levels  5  }

    modulePlatform  OBJECT-TYPE
        SYNTAX          Integer32
        MAX-ACCESS      read-only
        STATUS          current
        DESCRIPTION
            "Debug level of the platform abstraction module"
        ::=  {  levels  6  }

    moduleHost  OBJECT-TYPE
        SYNTAX          Integer32
        MAX-ACCESS      read-only
        STATUS          current
        DESCRIPTION
            "Debug level of the host application"
        ::=  {  levels  7  }

    dataRcvChunkSize    OBJECT-TYPE
        SYNTAX          Integer32
        MAX-ACCESS      read-write
        STATUS          current
        DESCRIPTION
            "Initial buffer size for received data"
        ::=  {  tcpTransport  1  }

    dataRcvMaxMemory    OBJECT-TYPE
        SYNTAX          Integer32
        MAX-ACCESS      read-write
        STATUS          current
        DESCRIPTION
            "Maximum memory used for received data"
        ::=  {  tcpTransport  2  }

    dataRcvInitialNumChunks OBJECT-TYPE
        SYNTAX          Integer32
        MAX-ACCESS      read-write
        STATUS          current
        DESCRIPTION
            "Initiail number of buffers allocated for received data"
        ::=  {  tcpTransport  3  }

    dataSndChunkSize    OBJECT-TYPE
        SYNTAX          Integer32
        MAX-ACCESS      read-write
        STATUS          current
        DESCRIPTION
            "Initial buffer size for sent data (control messages only)"
        ::=  {  tcpTransport  4  }

    dataSndMaxMemory    OBJECT-TYPE
        SYNTAX          Integer32
        MAX-ACCESS      read-write
        STATUS          current
        DESCRIPTION
            "Maximum memory used by sent data (control messages only)"
        ::=  {  tcpTransport  5  }

    dataSndInitialNumChunks OBJECT-TYPE
        SYNTAX          Integer32
        MAX-ACCESS      read-write
        STATUS          current
        DESCRIPTION
            "Initial number of buffers allocated for sent data (control messages only)"
        ::=  {  tcpTransport  6  }

    sendBuffersChunkSize    OBJECT-TYPE
        SYNTAX          Integer32
        MAX-ACCESS      read-write
        STATUS          current
        DESCRIPTION
            "Initial buffer size for storing references to buffers to be sent"
        ::=  {  tcpTransport  7  }

    sendBuffersMaxMemory    OBJECT-TYPE
        SYNTAX          Integer32
        MAX-ACCESS      read-write
        STATUS          current
        DESCRIPTION
            "Maximum memory used by buffer references"
        ::=  {  tcpTransport  8  }

    sendBuffersInitialNumChunks OBJECT-TYPE
        SYNTAX          Integer32
        MAX-ACCESS      read-write
        STATUS          current
        DESCRIPTION
            "Initial number of buffers allocated for holding references"
        ::=  {  tcpTransport  9  }

    flushInterval   OBJECT-TYPE
        SYNTAX          Integer32
        MAX-ACCESS      read-write
        STATUS          current
        DESCRIPTION
            "Interval between flushes of queued data"
        ::=  {  tcpTransport  10  }

END
